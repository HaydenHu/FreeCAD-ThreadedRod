# -*- coding: utf-8 -*-
# Macro: ThreadedRod
# 图标: 螺丝柱
# 功能: 选中圆柱面，利用 FreeCAD 自带的 Hole(螺纹孔)生成螺纹环套，
#       再通过布尔差集在圆柱上切出外螺纹。
#
# 使用方法:
#   1. 在 Part 或 PartDesign 工作台中选中一个圆柱面
#   2. 运行此宏
#   3. 选择螺纹规格或自定义参数，确认执行

import FreeCAD as App
import FreeCADGui as Gui
import Part
from FreeCAD import Vector
from PySide import QtGui, QtCore
import math


# ── 标准公制粗牙螺纹参数 (公称直径, 螺距) ──
METRIC_THREADS = {
    "M2":   (2.0,  0.40),
    "M2.5": (2.5,  0.45),
    "M3":   (3.0,  0.50),
    "M4":   (4.0,  0.70),
    "M5":   (5.0,  0.80),
    "M6":   (6.0,  1.00),
    "M8":   (8.0,  1.25),
    "M10":  (10.0, 1.50),
    "M12":  (12.0, 1.75),
    "M14":  (14.0, 2.00),
    "M16":  (16.0, 2.00),
    "M18":  (18.0, 2.50),
    "M20":  (20.0, 2.50),
    "M22":  (22.0, 2.50),
    "M24":  (24.0, 3.00),
    "M27":  (27.0, 3.00),
    "M30":  (30.0, 3.50),
    "M33":  (33.0, 3.50),
    "M36":  (36.0, 4.00),
    "M39":  (39.0, 4.00),
    "M42":  (42.0, 4.50),
    "M45":  (45.0, 4.50),
    "M48":  (48.0, 5.00),
    "M52":  (52.0, 5.00),
    "M56":  (56.0, 5.50),
    "M60":  (60.0, 5.50),
    "M64":  (64.0, 6.00),
    "M68":  (68.0, 6.00),
}


def find_body(obj):
    """查找特征所属的 PartDesign Body."""
    if obj.TypeId == 'PartDesign::Body':
        return obj
    for p in obj.InList:
        if p.TypeId == 'PartDesign::Body':
            return p
    try:
        g = obj.getParentGroup()
        if g and g.TypeId == 'PartDesign::Body':
            return g
    except Exception:
        pass
    return None


def get_cylindrical_face_info(face):
    """从圆柱面提取半径、轴线和高度信息."""
    surf = face.Surface
    if not hasattr(surf, 'Radius'):
        return None

    radius = surf.Radius
    center = surf.Center
    axis = surf.Axis.normalize()

    verts = [v.Point for v in face.Vertexes]
    if len(verts) < 2:
        return None

    projections = [axis.dot(v - center) for v in verts]
    min_p = min(projections)
    max_p = max(projections)
    height = max_p - min_p
    if height < 0.001:
        return None

    axis_start = center + axis * min_p
    axis_end = center + axis * max_p

    return {
        'radius': radius,
        'axis': axis,
        'height': height,
        'axis_start': axis_start,
        'axis_end': axis_end,
    }


def suggest_thread(info):
    """根据圆柱半径推荐最接近的公制螺纹."""
    r = info['radius']
    best_key = None
    best_diff = float('inf')
    for key, (nom_d, pitch) in METRIC_THREADS.items():
        diff = abs(nom_d / 2.0 - r)
        if diff < best_diff:
            best_diff = diff
            best_key = key
    if best_diff < r * 0.3:
        return best_key, best_diff
    return None, best_diff


def create_thread_cutter(doc, nom_diameter, pitch, cutter_length, cutter_radius):
    """
    利用 PartDesign Hole 创建一个螺纹切刀体。
    """
    # 临时 Body
    body = doc.addObject("PartDesign::Body", "_ThreadCutterBody")

    # 大圆柱
    cyl = doc.addObject("PartDesign::AdditiveCylinder", "_CutterBase")
    cyl.Radius = cutter_radius
    cyl.Height = cutter_length
    cyl.Angle = 360
    body.addObject(cyl)
    doc.recompute()

    # 找到圆柱顶面用于 sketch 附着
    import Sketcher
    face_name = "Face2"
    for i, f in enumerate(cyl.Shape.Faces):
        try:
            dist = f.distToShape(Part.Vertex(Vector(0, 0, cutter_length)))
            if abs(dist[0]) < 0.01:
                face_name = "Face{}".format(i + 1)
                break
        except Exception:
            continue

    sketch = doc.addObject("Sketcher::SketchObject", "_CutterSketch")
    body.addObject(sketch)
    sketch.AttachmentSupport = (cyl, face_name)
    sketch.MapMode = "FlatFace"
    doc.recompute()

    geo_list = []
    geo_list.append(Part.Circle())
    geo_list[0].Radius = nom_diameter / 2.0
    sketch.addGeometry(geo_list, False)
    sketch.addConstraint(Sketcher.Constraint("Coincident", 0, 3, -1, 1))
    doc.recompute()

    hole = doc.addObject("PartDesign::Hole", "_CutterHole")
    body.addObject(hole)
    hole.Profile = sketch
    hole.Diameter = nom_diameter
    hole.Depth = cutter_length + pitch * 1.5
    hole.DepthType = 0
    hole.DrillPoint = 0
    hole.Threaded = 1
    hole.ModelThread = 1
    hole.ThreadType = 1
    hole.ThreadDepthType = 0
    hole.ThreadDirection = 0
    hole.ThreadClass = 0
    hole.HoleCutType = 0
    hole.Tapered = 0
    hole.Reversed = 0
    hole.Refine = True

    # ── ThreadType 枚举: 1=ISOMetricProfile(粗牙), 2=ISOMetricFineProfile(细牙) ──
    THREAD_TYPE_COARSE = 1
    THREAD_TYPE_FINE = 2

    def find_thread_size(hole_obj, thread_type, nom_d, pt):
        hole_obj.ThreadType = thread_type
        sizes = hole_obj.getEnumerationsOfProperty("ThreadSize")
        best = None
        best_score = float('inf')
        for s in sizes:
            sl = s.lower()
            if sl.startswith("m") and "x" in sl:
                try:
                    parts = sl[1:].split("x")
                    d = float(parts[0].strip())
                    p = float(parts[1].strip())
                    if abs(d - nom_d) < 0.02:
                        score = abs(p - pt)
                        if score < best_score:
                            best_score = score
                            best = s
                except (ValueError, IndexError):
                    continue
        return best, best_score

    match_coarse, score_coarse = find_thread_size(hole, THREAD_TYPE_COARSE, nom_diameter, pitch)
    match_fine, score_fine = find_thread_size(hole, THREAD_TYPE_FINE, nom_diameter, pitch)

    if match_fine and (not match_coarse or score_fine <= score_coarse):
        hole.ThreadType = THREAD_TYPE_FINE
        sizes = hole.getEnumerationsOfProperty("ThreadSize")
        hole.ThreadSize = sizes.index(match_fine)
    elif match_coarse:
        hole.ThreadType = THREAD_TYPE_COARSE
        sizes = hole.getEnumerationsOfProperty("ThreadSize")
        hole.ThreadSize = sizes.index(match_coarse)
    else:
        sizes_str = ", ".join(hole.getEnumerationsOfProperty("ThreadSize")[:10])
        raise RuntimeError(
            f"Cannot find matching thread size for M{nom_diameter:.0f}x{pitch:.2f}. "
            f"Available in coarse: {sizes_str}")

    doc.recompute()

    # 返回 Body 和 Hole 对象名，用于 make_cut
    return body.Name, hole.Name, body


def main():
    doc = App.ActiveDocument
    if not doc:
        QtGui.QMessageBox.warning(None, "错误", "请先打开文档。")
        return

    sel = Gui.Selection.getSelectionEx()
    if not sel:
        QtGui.QMessageBox.warning(None, "错误", "请先选中一个圆柱面。")
        return

    # 提取选中的面 — 圆柱面(螺纹面) + 圆面(起始参考)
    face_info = None
    source_obj = None
    ref_face_center = None  # 参考圆面的中心点 (世界坐标)
    ref_face_normal = None  # 参考圆面的法向

    for s in sel:
        if not hasattr(s.Object, 'Shape'):
            continue
        for sn in s.SubElementNames:
            if sn.startswith('Face'):
                try:
                    f = s.Object.Shape.getElement(sn)
                    # 检查是否是圆柱面
                    cyl_info = get_cylindrical_face_info(f)
                    if cyl_info:
                        face_info = cyl_info
                        source_obj = s.Object
                    elif ref_face_center is None and hasattr(f.Surface, 'Axis'):
                        # 平面（圆面/环面）→ 可以作为起始参考（取第一个）
                        ref_face_center = f.CenterOfMass
                        ref_face_normal = f.Surface.Axis.normalize()
                except Exception:
                    pass

    if not face_info:
        QtGui.QMessageBox.warning(None, "错误",
            "未检测到有效的圆柱面。\n请选中螺丝柱的外圆柱面。")
        return

    # 验证参考面法向是否与圆柱轴平行（同向或反向）
    has_ref_face = False
    if ref_face_center is not None and ref_face_normal is not None:
        axis = face_info['axis']
        dot = abs(ref_face_normal.dot(axis))
        if abs(dot - 1.0) < 0.01:
            has_ref_face = True

    body = find_body(source_obj)

    # ── 对话框 ──
    dlg = QtGui.QDialog()
    dlg.setWindowTitle("螺丝柱外螺纹 Threaded Rod")
    dlg.setMinimumWidth(420)
    dlg.setModal(True)
    layout = QtGui.QVBoxLayout()

    layout.addWidget(QtGui.QLabel(
        f"<b>选中圆柱:</b><br>"
        f"  半径: {face_info['radius']:.3f} mm<br>"
        f"  高度: {face_info['height']:.3f} mm"))
    layout.addSpacing(8)

    # 推荐螺纹
    suggested, diff = suggest_thread(face_info)
    suggest_label = QtGui.QLabel("")
    if suggested:
        suggest_label.setText(
            f"<span style='color:#228833;'>推荐: {suggested} "
            f"(外径={METRIC_THREADS[suggested][0]} mm, "
            f"螺距={METRIC_THREADS[suggested][1]} mm)</span>")
    else:
        suggest_label.setText(
            "<span style='color:#cc8800;'>未找到匹配的标准螺纹，请自定义。</span>")
    suggest_label.setTextFormat(QtCore.Qt.RichText)
    layout.addWidget(suggest_label)
    layout.addSpacing(8)

    # ── 从 Hole 获取粗牙/细牙的实际 ThreadSize 枚举 ──
    dummy_doc = App.newDocument("_ThreadTemp")
    dummy_body = dummy_doc.addObject("PartDesign::Body", "_TmpBody")
    dummy_cyl = dummy_doc.addObject("PartDesign::AdditiveCylinder", "_TmpCyl")
    dummy_cyl.Radius = 10; dummy_cyl.Height = 10
    dummy_body.addObject(dummy_cyl)
    dummy_sk = dummy_doc.addObject("Sketcher::SketchObject", "_TmpSk")
    dummy_body.addObject(dummy_sk)
    dummy_sk.AttachmentSupport = (dummy_cyl, "Face2")
    dummy_sk.MapMode = "FlatFace"
    dummy_doc.recompute()
    dummy_hole = dummy_doc.addObject("PartDesign::Hole", "_TmpHole")
    dummy_body.addObject(dummy_hole)
    dummy_hole.Profile = dummy_sk
    dummy_hole.Threaded = 1

    # 粗牙
    dummy_hole.ThreadType = 1
    coarse_sizes = dummy_hole.getEnumerationsOfProperty("ThreadSize")
    # 细牙
    dummy_hole.ThreadType = 2
    fine_sizes = dummy_hole.getEnumerationsOfProperty("ThreadSize")
    App.closeDocument(dummy_doc.Name)

    # ── 解析外径/螺距 ──
    def parse_thread_sizes(sizes):
        result = []
        for s in sizes:
            sl = s.lower()
            if sl.startswith("m") and "x" in sl:
                try:
                    parts = sl[1:].split("x")
                    d = float(parts[0].strip())
                    p = float(parts[1].strip())
                    result.append((s, d, p))
                except (ValueError, IndexError):
                    continue
        return sorted(result, key=lambda x: x[1])

    coarse_parsed = parse_thread_sizes(coarse_sizes)
    fine_parsed = parse_thread_sizes(fine_sizes)

    # ── 标准选择 — ThreadType ──
    type_layout = QtGui.QHBoxLayout()
    type_layout.addWidget(QtGui.QLabel("标准:"))
    type_combo = QtGui.QComboBox()
    type_combo.addItem("自定义")
    type_combo.addItem("ISO 公制粗牙 (ISO Metric Coarse)")
    type_combo.addItem("ISO 公制细牙 (ISO Metric Fine)")
    type_layout.addWidget(type_combo)
    type_layout.addStretch()
    layout.addLayout(type_layout)

    # ── 标准选择 — ThreadSize ──
    size_layout = QtGui.QHBoxLayout()
    size_label = QtGui.QLabel("大小:")
    size_layout.addWidget(size_label)
    size_combo = QtGui.QComboBox()
    size_combo.setMinimumWidth(200)
    size_layout.addWidget(size_combo)
    size_layout.addStretch()
    layout.addLayout(size_layout)

    # ── 自定义参数（标准模式下隐藏，自定义模式显示） ──
    custom_widget = QtGui.QWidget()
    custom_layout = QtGui.QVBoxLayout()
    custom_layout.setContentsMargins(0, 0, 0, 0)

    diam_layout = QtGui.QHBoxLayout()
    diam_layout.addWidget(QtGui.QLabel("公称外径 (mm):"))
    diam_spin = QtGui.QDoubleSpinBox()
    diam_spin.setRange(1.0, 300.0)
    diam_spin.setDecimals(3)
    diam_spin.setSingleStep(0.5)
    diam_spin.setValue(face_info['radius'] * 2.0)
    diam_layout.addWidget(diam_spin)
    custom_layout.addLayout(diam_layout)

    pitch_layout = QtGui.QHBoxLayout()
    pitch_layout.addWidget(QtGui.QLabel("螺距 (mm):"))
    pitch_spin = QtGui.QDoubleSpinBox()
    pitch_spin.setRange(0.1, 20.0)
    pitch_spin.setDecimals(2)
    pitch_spin.setSingleStep(0.05)
    pitch_spin.setValue(1.0)
    pitch_layout.addWidget(pitch_spin)
    custom_layout.addLayout(pitch_layout)

    custom_widget.setLayout(custom_layout)
    layout.addWidget(custom_widget)

    # ── 设置 ThreadSize 列表 ──
    def set_size_combo(parsed_list, select_d=None):
        size_combo.clear()
        for s, d, p in parsed_list:
            size_combo.addItem(f"M{d:.0f}×{p:.2f}  (外径={d}mm, 螺距={p}mm)")
        # 选中最接近建议的
        if select_d is not None and len(parsed_list) > 0:
            best_i = 0
            best_diff = float('inf')
            for i, (s, d, p) in enumerate(parsed_list):
                diff = abs(d - select_d)
                if diff < best_diff:
                    best_diff = diff
                    best_i = i
            size_combo.setCurrentIndex(best_i)

    # 推荐直径
    suggested_d = face_info['radius'] * 2.0
    if suggested:
        suggested_d = METRIC_THREADS[suggested][0]

    # 默认选粗牙 — 手动设初始状态（信号尚未连接，setCurrentIndex 不会触发）
    type_combo.setCurrentIndex(1)
    set_size_combo(coarse_parsed, suggested_d)
    custom_widget.setVisible(False)
    size_combo.setEnabled(True)

    def on_type_changed(idx):
        if idx == 0:
            size_label.setVisible(False)
            size_combo.setVisible(False)
            custom_widget.setVisible(True)
            size_combo.clear()
        elif idx == 1:
            size_label.setVisible(True)
            size_combo.setVisible(True)
            custom_widget.setVisible(False)
            set_size_combo(coarse_parsed, suggested_d)
        elif idx == 2:
            size_label.setVisible(True)
            size_combo.setVisible(True)
            custom_widget.setVisible(False)
            set_size_combo(fine_parsed, suggested_d)

    type_combo.currentIndexChanged.connect(on_type_changed)

    # 螺纹长度
    len_layout = QtGui.QHBoxLayout()
    len_layout.addWidget(QtGui.QLabel("螺纹长度 (mm):"))
    len_spin = QtGui.QDoubleSpinBox()
    len_spin.setRange(0.1, 9999.0)
    len_spin.setDecimals(2)
    len_spin.setSingleStep(1.0)
    len_spin.setValue(face_info['height'])
    len_layout.addWidget(len_spin)
    layout.addLayout(len_layout)

    # 起始偏移 — 仅当选了参考圆面时可用
    ref_face_note = QtGui.QLabel("(选中了参考圆面，螺纹将从该面偏移指定距离开始)")
    ref_face_note.setStyleSheet("color: #228833;")
    if not has_ref_face:
        ref_face_note.setText("(未检测到参考圆面，螺纹从圆柱起点开始)")
        ref_face_note.setStyleSheet("color: #888;")
    layout.addWidget(ref_face_note)

    offset_layout = QtGui.QHBoxLayout()
    offset_layout.addWidget(QtGui.QLabel("起始偏移 (mm):"))
    offset_spin = QtGui.QDoubleSpinBox()
    offset_spin.setRange(-9999.0, 9999.0)
    offset_spin.setDecimals(2)
    offset_spin.setSingleStep(1.0)
    offset_spin.setValue(0.0)
    offset_spin.setToolTip("正值 = 向参考面外侧偏移\n"
                          "负值 = 向参考面内侧偏移\n"
                          "仅当选了参考圆面时有效")
    if not has_ref_face:
        offset_spin.setEnabled(False)
    offset_layout.addWidget(offset_spin)
    layout.addLayout(offset_layout)

    # 螺纹旋向
    handed_layout = QtGui.QHBoxLayout()
    handed_layout.addWidget(QtGui.QLabel("旋向:"))
    handed_combo = QtGui.QComboBox()
    handed_combo.addItem("右旋 (标准)")
    handed_combo.addItem("左旋")
    handed_layout.addWidget(handed_combo)
    handed_layout.addStretch()
    layout.addLayout(handed_layout)

    layout.addSpacing(8)

    btn_layout = QtGui.QHBoxLayout()
    ok = QtGui.QPushButton("创建外螺纹")
    ok.clicked.connect(dlg.accept)
    cancel = QtGui.QPushButton("取消")
    cancel.clicked.connect(dlg.reject)
    btn_layout.addWidget(ok)
    btn_layout.addWidget(cancel)
    layout.addLayout(btn_layout)
    dlg.setLayout(layout)

    if dlg.exec_() != QtGui.QDialog.Accepted:
        return

    # 获取参数 — 标准模式从 combo 取，自定义模式从 spin 取
    type_idx = type_combo.currentIndex()
    if type_idx == 0:
        nom_diameter = diam_spin.value()
        pitch = pitch_spin.value()
    elif type_idx == 1:
        _, nom_diameter, pitch = coarse_parsed[size_combo.currentIndex()]
    else:
        _, nom_diameter, pitch = fine_parsed[size_combo.currentIndex()]

    thread_length = len_spin.value()
    is_left_handed = (handed_combo.currentIndex() == 1)

    if nom_diameter <= 0 or pitch <= 0 or thread_length <= 0:
        QtGui.QMessageBox.warning(None, "错误", "参数无效。")
        return

    doc.openTransaction("Threaded Rod")
    try:
        # ── 步骤 1: 创建螺纹切刀体 (Body + Hole with ModelThread) ──
        cutter_radius = nom_diameter / 2.0 + max(pitch * 2, 5.0)
        cutter_body_name, cutter_hole_name, cutter_body = create_thread_cutter(
            doc, nom_diameter, pitch, thread_length, cutter_radius)

        # ── 步骤 2: body 移动到用户圆柱位置/角度 ──
        axis = face_info['axis']
        start_pt = face_info['axis_start']
        z_axis = Vector(0, 0, 1)

        # 如果没有参考圆面，从圆柱起点开始；有参考面则从参考面开始
        if has_ref_face:
            # 直接使用参考面中心投影到轴上的点作为起点
            start_pt_on_axis = axis.dot(ref_face_center - start_pt)
            start_pt = start_pt + axis * start_pt_on_axis

        start_offset = offset_spin.value()
        # 无参考面时沿用 pitch*0.5 偏移
        if not has_ref_face:
            start_pt = start_pt - axis * (pitch * 0.5)

        placement = App.Placement()
        placement.Base = start_pt + axis * start_offset

        # 轴对齐旋转
        if abs(axis.dot(z_axis) - 1.0) > 1e-7:
            rot_axis = z_axis.cross(axis)
            if rot_axis.Length > 1e-7:
                rot_axis.normalize()
                ang = math.acos(z_axis.dot(axis))
                placement.Rotation = App.Rotation(rot_axis, math.degrees(ang))

        # 绕轴旋转黄金角度避免 0°/90° 对齐导致布尔卡死
        twist = App.Rotation(axis, 37.5)
        placement.Rotation = twist.multiply(placement.Rotation)


        cutter_body.Placement = placement
        doc.recompute()

        # ── 步骤 3: 低阶布尔 — 用户圆柱 .cut(cutter_body.Shape) = 外螺纹 ──
        result_shape = source_obj.Shape.cut(cutter_body.Shape)

        if result_shape is None or result_shape.isNull():
            raise RuntimeError("布尔切割失败。请检查螺纹直径是否合理。")

        # ── 步骤 4: 输出结果 (放回用户的 PartDesign Body) ──
        if body:
            # 直接在 Body 中创建一个特征替换原来的 shape
            result_obj = doc.addObject('PartDesign::Feature', 'ThreadedRod')
            result_obj.Shape = result_shape
            result_obj.Label = f"ThreadedRod_M{nom_diameter:.0f}x{pitch:.2f}"
            body.addObject(result_obj)
            # 隐藏原来的 source_obj feature
            source_obj.Visibility = False
        else:
            source_obj.Shape = result_shape

        doc.recompute()

        # ── 步骤 5: 隐藏临时 Body ──
        cutter_body.Visibility = False
        for o in cutter_body.Group:
            o.Visibility = False

        doc.commitTransaction()

        QtGui.QMessageBox.information(None, "完成",
            f"外螺纹创建成功！\n\n"
            f"规格: M{nom_diameter:.0f}x{pitch:.2f}\n"
            f"长度: {thread_length:.2f} mm\n"
            f"旋向: {'左旋' if is_left_handed else '右旋'}")

    except Exception as e:
        doc.abortTransaction()
        QtGui.QMessageBox.critical(None, "失败",
            f"创建外螺纹失败:\n\n{str(e)}")


if __name__ == '__main__':
    main()
